package 'Stakeholders'
{
    // ====================================
    // Definition of stakeholders
    // ====================================
    part def EPS_team; // The team responsible for developing and maintaining the EPS system
    part def SPS; // Smart EPS
    part def OBC;
}
