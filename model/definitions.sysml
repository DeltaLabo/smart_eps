package 'System Definitions'
{
    // ====================================
    // Definition of Systems
    // ====================================
    part def SAT; // The whole satellite
    part def SPS; // Smart EPS
    part def OBC;
}
